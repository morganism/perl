GPRS-PGW-Charging-DataTypes-REL8 DEFINITIONS IMPLICIT TAGS ::=
BEGIN

------------------------------------------------------------------------------
--
--  GPRS RECORDS
--
-- 3GPP 32.298V8.5.0 AND 3GPP 32.251V8.6.0
------------------------------------------------------------------------------

GPRSRecord ::= CHOICE 
--
-- Record values 20, 22..27 are specific
-- Record values 76..77 are MBMS specific
-- Record values 78..79 are EPC specific 
{
  pgwRecord[79] PGWRecord 
}

PGWRecord 	::= SET
{
  recordType			[0] RecordType,
  servedIMSI			[3] IMSI,
  p-GWAddress			[4] GSNAddress,
  chargingID			[5] ChargingID,
  servingNodeAddress		[6] SEQUENCE OF GSNAddress,
  accessPointNameNI		[7] AccessPointNameNI OPTIONAL,
  pdpPDNType			[8] PDPType OPTIONAL,
  servedPDPPDNAddress	        [9] PDPAddress OPTIONAL,
  dynamicAddressFlag		[11] DynamicAddressFlag OPTIONAL,
  recordOpeningTime		[13] TimeStamp,
  duration		        [14] CallDuration,
  causeForRecClosing		[15] CauseForRecClosing,
  diagnostics			[16] Diagnostics OPTIONAL,
  recordSequenceNumber	        [17] INTEGER OPTIONAL,
  nodeID		        [18] NodeID OPTIONAL,
  localSequenceNumber	        [20] LocalSequenceNumber OPTIONAL,
  apnSelectionMode		[21] APNSelectionMode OPTIONAL,
  servedMSISDN		        [22] MSISDN OPTIONAL,
  chargingCharacteristics	[23] ChargingCharacteristics,
  chChSelectionMode		[24] ChChSelectionMode OPTIONAL,
  servingNodePLMNIdentifier	[27] PLMN-Id OPTIONAL,
  servedIMEISV		        [29] IMEI OPTIONAL,
  rATType			[30] RATType OPTIONAL,
  mSTimeZone 			[31] MSTimeZone OPTIONAL,
  userLocationInformation	[32] OCTET STRING OPTIONAL,
  listOfServiceData	        [34] SEQUENCE OF ChangeOfServiceCondition OPTIONAL,
  servingNodeType				[35] SEQUENCE OF ServingNodeType,
  servedMNNAI					[36] SubscriptionID OPTIONAL,
  p-GWPLMNIdentifier			[37] PLMN-Id OPTIONAL,
  startTime					[38] TimeStamp OPTIONAL,
  stopTime					[39] TimeStamp OPTIONAL,
  pDNConnectionID				[41] ChargingID OPTIONAL
}

AccessPointNameNI::= IA5String (SIZE(1..63))
	--
	-- Network Identifier part of APN in  dot representation.
	-- For example, if the complete APN is 'apn1a.apn1b.apn1c.mnc022.mcc111.gprs'
	-- NI is 'apn1a.apn1b.apn1c' and is presented in this form in the CDR..


APNSelectionMode::= ENUMERATED
{
	--
	-- See Information Elements TS 29.060, TS 29.274 or TS 29.275
	--
	mSorNetworkProvidedSubscriptionVerified	   (0),
	mSProvidedSubscriptionNotVerified	         (1),
	networkProvidedSubscriptionNotVerified	   (2)
}

CallDuration::= INTEGER
        --
        -- The call duration is counted in seconds.
        -- For successful calls /sessions / PDP contexts, this is the chargeable duration.
        -- For call attempts this is the call holding time.
        --


CauseForRecClosing	::= INTEGER
{
	--
	-- In PGW-CDR and SGW-CDR the value servingNodeChange is used for partial record
	-- generation due to Serving Node Address list Overflow
	-- In SGSN servingNodeChange indicates the SGSN change
	-- 	
	-- LCS related causes belong to the MAP error causes acc. TS 29.002
	--
	-- cause codes 0 to 15 are defined 'CauseForTerm' (cause for termination)
	-- All cause values are not relevent to SGW. Refer the spec to find out the
       -- cause values for SGW.
	normalRelease			 (0),
	abnormalRelease		       (4),
	volumeLimit		             (16),
	timeLimit			       (17),
	servingNodeChange		       (18),
	maxChangeCond			 (19),
	managementIntervention         (20),
	rATChange			       (22),
	mSTimeZoneChange		       (23),
	sGSNPLMNIDChange 		       (24)
}

ChangeOfServiceCondition	::= SEQUENCE
{
	--
	-- Used for Flow based Charging service data container
	--
	ratingGroup 					[1] RatingGroupId,
	chargingRuleBaseName			[2] ChargingRuleBaseName OPTIONAL,
    resultCode						[3] ResultCode OPTIONAL,
	localSequenceNumber				[4] LocalSequenceNumber OPTIONAL,
	timeOfFirstUsage				[5] TimeStamp OPTIONAL,
	timeOfLastUsage					[6] TimeStamp OPTIONAL,
	timeUsage 						[7] CallDuration OPTIONAL,
	serviceConditionChange			[8] ServiceConditionChange,
	qoSInformationNeg				[9] EPCQoSInformation OPTIONAL,
	servingNodeAddress 				[10] GSNAddress OPTIONAL,
	datavolumeFBCUplink				[12] DataVolumeGPRS OPTIONAL,
	datavolumeFBCDownlink			[13] DataVolumeGPRS OPTIONAL,
	timeOfReport					[14] TimeStamp,
    failureHandlingContinue			[16] FailureHandlingContinue OPTIONAL,
	serviceIdentifier				[17] ServiceIdentifier OPTIONAL,
	userLocationInformation			[20] OCTET STRING OPTIONAL
}



ChargingCharacteristics	::= OCTET STRING (SIZE(2))
    --
    -- Bit 0-3:  Profile Index
    -- Bit 4-15: Behavior
    --   

ChargingID	::= INTEGER (0..4294967295)
	--	
	-- Generated in P-GW, part of IP CAN bearer	
	-- 0..4294967295 is equivalent to 0..2**32-1
	--

ChargingRuleBaseName	::= IA5String (SIZE(1..16))
	-- 
	-- identifier for the group of charging rules
	-- see Charging-Rule-Base-Name AVP as defined in TS 29.212
	--
	
ChChSelectionMode		::= ENUMERATED
{
	servingNodeSupplied	(0),	-- For S-GW/P-GW
	homeDefault		      (3),	-- For SGSN, S-GW and P-GW
	roamingDefault	      (4),	-- For SGSN, S-GW and P-GW	
	visitingDefault	      (5)	-- For SGSN, S-GW and P-GW
}

DataVolumeGPRS	::= INTEGER
	--
	-- The volume of data transferred in octets.
	--

DynamicAddressFlag	::= BOOLEAN


EPCQoSInformation	::= SEQUENCE
{
   --
   -- See TS 29.212 [88] for more information
   -- 
   qCI			        [1] INTEGER,
   maxRequestedBandwithUL	[2] INTEGER OPTIONAL,
   maxRequestedBandwithDL	[3] INTEGER OPTIONAL,
   guaranteedBitrateUL	        [4] INTEGER OPTIONAL,
   guaranteedBitrateDL	        [5] INTEGER OPTIONAL,
   aRP				[6] INTEGER OPTIONAL
}
FailureHandlingContinue  ::= BOOLEAN
	--
-- This parameter is included when the failure handling procedure has been executed and new 
-- containers are opened. This parameter shall be included in the first and subsequent 
-- containers opened after the failure handling execution.
	--


GSNAddress::= IPAddress

--IA5String::= OCTET STRING

NodeID	::= IA5String (SIZE(1..20))



PDPAddress	::= CHOICE
{
	iPAddress	[0] IPAddress
	--
    -- eTSIAddress as specified in 32.298 is not supported
    --
}

PDPType		::= OCTET STRING (SIZE(2))
	--
	-- OCTET 1: PDP Type Organization
	-- OCTET 2: PDP Type Number
	-- See TS 29.060 for GTP, TS 29.274 for eGTP and TS 29.275 for PMIP
	--

PLMN-Id		::= OCTET STRING (SIZE (3))
	--
	--	This is a 1:1 copy from the Routing Area Identity (RAI) IE specified in TS 29.060
	--      as follows:
	--	OCTET 1 of PLMN-Id = OCTET 2 of RAI  
	--	OCTET 2 of PLMN-Id = OCTET 3 of RAI  
	--	OCTET 3 of PLMN-Id = OCTET 4 of RAI  
	--

RatingGroupId ::= INTEGER



RATType	::= INTEGER (0..255)
	--
	-- Ihis integer is 1:1 copy of the RAT type value as defined in TS 29.060 for GTP, 
	-- TS 29.274 for eGTP and TS 29.275 for PMIP.
	--

RecordType 	::= INTEGER 
{
  --	Record values 0..17 are CS specific.
  --	The contents are defined in TS 32.250

  pGWRecord     (85)
}

ResultCode ::= INTEGER
	-- charging protocol return value, range of 4 byte (0...4294967259)
	-- see Result-Code AVP as used in 3GPP 32.299
	--


ServiceConditionChange	::= BIT STRING 
{
	qoSChange 								 (0),	-- bearer modification
	sGSNChange 								 (1), 	-- bearer modification
	sGSNPLMNIDChange 						 (2), 	-- bearer modification
	tariffTimeSwitch 						 (3), 	-- tariff time change
	pDPContextRelease 						 (4), 	-- bearer release
	rATChange 								 (5),	-- bearer modification
	serviceIdledOut 						 (6),	-- IP flow idle out, DCCA QHT expiry
	reserved1 								 (7),	-- old: QCTexpiry is no report event
	configurationChange 					 (8),	-- configuration change
	serviceStop 							 (9), 	-- IP flow termination
	dCCATimeThresholdReached 				(10),	-- DCCA quota reauthorization
	dCCAVolumeThresholdReached 				(11), 	-- DCCA quota reauthorization
	dCCAServiceSpecificUnitThresholdReached	(12), 	-- DCCA quota reauthorization
	dCCATimeExhausted 						(13), 	-- DCCA quota reauthorization
	dCCAVolumeExhausted 					(14), 	-- DCCA quota reauthorization
	dCCAValidityTimeout 					(15), 	-- DCCA quota validity time (QVT expiry)
	reserved2								(16),	-- reserved due to no use case, 
													-- old: return Requested is covered by (17),(18)
	dCCAReauthorisationRequest 				(17), 	-- DCCA quota reauthorization request by OCS
	dCCAContinueOngoingSession 				(18), 	-- DCCA failure handling (CCFH), continue IP flow
	dCCARetryAndTerminateOngoingSession		(19), 	-- DCCA failure handling (CCFH), terminate IP flow after DCCA retry
	dCCATerminateOngoingSession 			(20), 	-- DCCA failure handling, terminate IP flow
	cGI-SAIChange							(21), 	-- bearer modification
	rAIChange								(22), 	-- bearer modification
	dCCAServiceSpecificUnitExhausted		(23), 	-- DCCA quota reauthorization
	recordClosure							(24),	-- PGW-CDR closure
	timeLimit								(25),	-- intermediate recording
	volumeLimit								(26),	-- intermediate recording
	serviceSpecificUnitLimit				(27),	-- intermediate recording
	envelopeClosure 						(28),	
	eCGIChange								(29), 	-- bearer modification. .ECGI Change.
	tAIChange								(30), 	-- bearer modification. .TAI Change.
	userLocationChange						(31)	-- bearer modification. .User Location Change.
} 

ServiceIdentifier ::= INTEGER (0..4294967295)
    --
    -- The service identifier is used to identify the service or the
    -- service component the service data flow relates to. See
    -- Service-Identifier AVP as defined in 3GPP TS 29.212

ServingNodeType	::= ENUMERATED
{
   sGSN	(0),
   pMIPSGW	(1),
   gTPSGW	(2),
   ePDG	(3),
   hSGW	(4),
   mME	(5)
}


SubscriptionID	::= SET
{
	subscriptionIDType	[0]	SubscriptionIDType,
	subscriptionIDData	[1]	UTF8String
}
SubscriptionIDType	::= ENUMERATED
{
	eND-USER-E164		(0),
	eND-USER-IMSI		(1),
	eND-USER-SIP-URI	(2),
	eND-USER-NAI		(3),
	eND-USER-PRIVATE	(4)
}

Diagnostics						::= CHOICE
{
    -- Only the option gsm0408Cause is used for this field
    --
    gsm0408Cause [0] INTEGER
}

IPAddress::= CHOICE
{
	iPBinaryAddress	        IPBinaryAddress

    --Currently only IPBinaryAddress is supported in PGWCDR
}

IPBinaryAddress::= CHOICE
{
	iPBinV4Address			[0] OCTET STRING (SIZE(4)),
	iPBinV6Address			[1] OCTET STRING (SIZE(16))
}



LocalSequenceNumber ::= INTEGER (0..4294967295)
	--
	-- Sequence number of the record in this node
	-- 0.. 4294967295 is equivalent to 0..2**32-1, unsigned integer in four octets


MSISDN::= ISDN-AddressString
        --
	-- See TS 23.003


MSTimeZone::= OCTET STRING (SIZE (2))
	--
	-- 1.Octet: Time Zone and 2. Octet: Daylight saving time, see TS 29.060


TimeStamp::= OCTET STRING (SIZE(9))
        --
        -- The contents of this field are a compact form of the UTCTime format
        -- containing local time plus an offset to universal time. Binary coded
        -- decimal encoding is employed for the digits to reduce the storage and
        -- transmission overhead
        -- e.g. YYMMDDhhmmssShhmm
        -- where
        -- YY   =       Year 00 to 99           BCD encoded
        -- MM   =       Month 01 to 12          BCD encoded
        -- DD   =       Day 01 to 31            BCD encoded
        -- hh   =       hour 00 to 23           BCD encoded
        -- mm   =       minute 00 to 59         BCD encoded
        -- ss   =       second 00 to 59         BCD encoded
        -- S    =       Sign 0 = "+", "-"       ASCII encoded
        -- hh   =       hour 00 to 23           BCD encoded
        -- mm   =       minute 00 to 59         BCD encoded
        --


TBCDSTRING ::= OCTET STRING
ISDN-AddressString ::= OCTET STRING
IMEI ::= TBCDSTRING (SIZE(8))
IMSI ::= TBCDSTRING (SIZE(3..8))
END
